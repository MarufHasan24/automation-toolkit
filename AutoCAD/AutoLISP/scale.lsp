(defun c:ScaleEachCenter (/ ss factor i obj minp maxp cen)
  (vl-load-com)
  (setq ss (ssget)
        factor (getreal "\nScale factor: "))
  (if (and ss factor)
    (repeat (setq i (sslength ss))
      (setq obj (vlax-ename->vla-object (ssname ss (setq i (1- i)))))
      (vla-GetBoundingBox obj 'minp 'maxp)
      (setq minp (vlax-safearray->list minp)
            maxp (vlax-safearray->list maxp)
            cen  (mapcar '(lambda (a b) (/ (+ a b) 2.0)) minp maxp))
      (vla-ScaleEntity obj (vlax-3d-point cen) factor)
    )
  )
  (princ)
)
